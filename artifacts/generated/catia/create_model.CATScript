' CATIA automation macro generated by Engineering Agent.
' Run with CATIA's macro runner on a licensed Windows workstation.
Language="VBSCRIPT"
Option Explicit

Dim document, part, body, shapeFactory
Set document = CATIA.Documents.Add("Part")
Set part = document.Part
Set body = part.Bodies.Add()
Set shapeFactory = part.ShapeFactory

' Model parameters (millimetres):
' wheelbase=2800
' front_track=1600
' rear_track=1580
' This macro creates a parametric skeleton; replace feature details with the
' team's CATPart template when production naming and datum conventions are known.
part.Update
document.SaveAs "vehicle_model.CATPart"
